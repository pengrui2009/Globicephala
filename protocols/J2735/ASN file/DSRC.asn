-- 
-- ASN.1 file for J2735-20170613.
-- Created by pr. base on the document CSAE distributed by 2017-06-13



-- The local module consisting of DEs / DFs and MSGs
DSRC DEFINITIONS
AUTOMATIC TAGS ::=
BEGIN
	
	-- Main message frame
	MessageFrame ::= CHOICE {
	bsmFrame	BasicSafetyMessage,
	mapFrame	MapData,
	rsmFrame	RoadsideSafetyMessage,
	spatFrame	SPAT,
	rsiFrame	RoadSideInformation,
	...
	}

	BasicSafetyMessage ::= SEQUENCE {
		msgCnt MsgCount,
		id OCTET STRING (SIZE(8)),
		-- vehicle ID
		plateNo OCTET STRING (SIZE(4..16)) OPTIONAL,
		-- Reserved for Electronic Vehicle Identification
		secMark DSecond,
		pos	Position3D,
		accuracy PositionConfidenceSet,
		transmission TransmissionState,
		speed Speed,
		heading Heading,
		angle SteeringWheelAngle OPTIONAL,
		motionCfd MotionConfidenceSet OPTIONAL,
		accelSet AccelerationSet4Way,
		brakes BrakeSystemStatus,
		size VehicleSize,
		vehicleClass VehicleClassification,
		-- VehicleClassification includes BasicVehicleClass and other extendible type
		safetyExt VehicleSafetyExtensions OPTIONAL,
		...
		}
	
	MapData ::= SEQUENCE {
		msgCnt	MsgCount,
		timeStamp MinuteOfTheYear OPTIONAL,
		nodes NodeList,
		--intersections or road endpoints,
		...
		}
		
	RoadSideInformation ::= SEQUENCE{
		msgCnt	MsgCount,
		timeStamp MinuteOfTheYear OPTIONAL,
		id	OCTET STRING(SIZE(8)),
		--RSU ID
		rsiId INTEGER (0..255),
		-- local ID of this rsi information set by RSU
		alertType AlertType,
		-- Text message warning or Traffic sign type according to China GB5768
		description IA5String (SIZE(1..256)) OPTIONAL,
		-- Text message if alertType = 0
		-- Additional description to the traffic sign if alertType > 0
		-- e.g. describe the subtype of the traffic sign
		priority Priority OPTIONAL,
		-- the urgency of this message, a relative
		-- degree of merit compared with other
		-- similar messages for this type (not other
		-- messages being sent by the device), nor a
		-- priority of display urgency
		refPos Position3D,
		-- Position of traffic alert (traffic sign or incident)
		alertPath PathPointList,
		-- Warning is active if vehicle is within this path
		-- Points are listed from upstream to downstream
		-- along the vehicle drive direction.
		-- One path includes at least two points.
		alertRadius Radius,
		-- The biggest distance away from the alert path
		-- within which the warning is active.
		...
	}
	
	RoadsideSafetyMessage ::= SEQUENCE {
		msgCnt MsgCount,
		id OCTET STRING (SIZE(8)),
		-- RSU ID
		refPos Position3D,
		-- Reference position of this RSM message
		participants ParticipantList,
		-- All or part of the participants
		-- detected by RSU
		...
	}

	SPAT ::= SEQUENCE {
		msgCnt MsgCount,
		timeStamp MinuteOfTheYear OPTIONAL,
		name DescriptiveName OPTIONAL,
		-- human readable name for this collection
		-- to be used only in debug mode
		intersections	IntersectionStateList,
		-- sets of SPAT data(one per intersection)
		...
	}		
	
	--DF_Element	
	--DF_AccelerationSet4Way
	AccelerationSet4Way ::= SEQUENCE {
		long Acceleration, -- Along the Vehicle Longitudinal axis
		lat Acceleration, -- Along the Vehicle Lateral axis
		vert VerticalAcceleration, -- Along the Vehicle Vertical axis
		yaw YawRate
		}
	
	--DE_BrakeSystemStatus
	BrakeSystemStatus ::= SEQUENCE {
		brakePadel	BrakePedalStatus OPTIONAL,
		wheelBrakes BrakeAppliedStatus OPTIONAL,
		traction TractionControlStatus OPTIONAL,
		abs AntiLockBrakeStatus OPTIONAL,
		scs StabilityControlStatus OPTIONAL,
		brakeBoost BrakeBoostApplied OPTIONAL,
		auxBrakes AuxiliaryBrakeStatus OPTIONAL
		}
		
	--DF_ConnectingLane
	ConnectingLane ::= SEQUENCE {
		lane LaneID, 
		-- Index of the connecting lane
		maneuver AllowedManeuvers OPTIONAL
		-- The Maneuver between
		-- the enclosing lane and this lane
		-- at the stop line to connect them
		}	
	
	--DF_Connection
	Connection::= SEQUENCE {
		remoteIntersection NodeReferenceID,
		-- This entry indicates the downstream intersection of the link this lane connects to.
		-- This provides a means to create meshes of lanes
		connectingLane ConnectingLane OPTIONAL,
		-- The index of the connecting lane and also
		-- the maneuver from the current lane to it
		-- When we want to list the allowed lanes of the next link
		-- this lane can lead to, we use this entry
		phaseId PhaseID OPTIONAL
		-- The matching signal group send by
		-- the SPAT message for this lane/maneuver.
		-- Shall be present unless the connectingLane
		-- has no signal group (is un-signalized)
		}
	
	--DF_ConnectsToList
	ConnectsToList ::= SEQUENCE (SIZE(1..8)) OF Connection
	
	--DF_DDateTime
	DDateTime	::= SEQUENCE {
		year DYear OPTIONAL,
		month DMonth OPTIONAL,
		day DDay OPTIONAL,
		hour DHour OPTIONAL,
		minute DMinute OPTIONAL,
		second DSecond OPTIONAL,
		offset DTimeOffset OPTIONAL --time zone
	}
	
	--DF_FullPositionVector
	FullPositionVector ::= SEQUENCE {
		utcTime DDateTime OPTIONAL, -- time with mSec precision
		pos Position3D,
		heading Heading OPTIONAL,
		transmission TransmissionState OPTIONAL,
		speed Speed OPTIONAL,
		posAccuracy PositionConfidenceSet OPTIONAL,
		timeConfidence TimeConfidence OPTIONAL,
		posConfidence PositionConfidenceSet OPTIONAL,
		motionCfd MotionConfidenceSet OPTIONAL,
		...
		}
	--DF_IntersectionState
	IntersectionState ::= SEQUENCE {
		intersectionId NodeReferenceID,
		-- A globally unique value set, consisting of a
		-- regionID and intersection ID assignment
		-- provides a unique mapping to the MAP Node
		status IntersectionStatusObject,
		-- general status of the controller(s)
		moy MinuteOfTheYear OPTIONAL,
		-- Minute of current UTC year
		-- used only with messages to be archived
		timeStamp DSecond OPTIONAL,
		-- the mSec point in the current UTC minute that
		-- this message was constructed
		phases PhaseList
		-- Each Movement is given in turn
		-- and contains its signal phase state,
		-- mapping to the lanes it applies to, and
		-- point in time it will end, and it
		-- may contain both active and future states
		}

	--DF_IntersectionStateList
	IntersectionStateList ::= SEQUENCE (SIZE(1..32)) OF IntersectionState
		
	--DF_Lane
	Lane ::= SEQUENCE {
		laneID LaneID,
		-- The unique ID number assigned
		-- to this lane object
		laneAttributes LaneAttributes OPTIONAL,
		-- Define basic attribute of lane
		maneuvers AllowedManeuvers OPTIONAL,
		-- the permitted maneuvers for this lane
		connectsTo ConnectsToList OPTIONAL,
		--connection to downstream lanes
		speedLimits SpeedLimitList OPTIONAL,
		-- List all the speed limits
		points PointList OPTIONAL,
		--Define road points and segments
		...
		}
		
	--DF_LaneAttributes
	LaneAttributes ::= SEQUENCE {
		shareWith LaneSharing OPTIONAL,
		laneType LaneTypeAttributes
		}
	
	--DF_LaneList
	LaneList ::= SEQUENCE (SIZE(1..32)) OF Lane
	
	--DE_LaneTypeAttributes
	LaneTypeAttributes ::= CHOICE {
		vehicle LaneAttributes-Vehicle, -- motor vehicle lanes
		crosswalk LaneAttributes-Crosswalk, -- pedestrian crosswalks
		bikeLane LaneAttributes-Bike, -- bike lanes
		sidewalk LaneAttributes-Sidewalk, -- pedestrian sidewalk paths
		median LaneAttributes-Barrier, -- medians & channelization
		striping LaneAttributes-Striping, -- roadway markings
		trackedVehicle LaneAttributes-TrackedVehicle, -- trains and trolleys
		parking LaneAttributes-Parking, -- parking and stopping lanes
		...
		}
	
	--DF_Link
	Link ::= SEQUENCE {
		name DescriptiveName OPTIONAL,
		-- Link name
		upstreamNodeId NodeReferenceID,
		-- this link is from upstreamNode to the Node it belongs to
		speedLimits SpeedLimitList OPTIONAL,
		-- List all the speed limits
		laneWidth LaneWidth,
		--Width of each lane
		points PointList OPTIONAL,
		--Define road points along the center of this link
		movements MovementList OPTIONAL,
		--Define movements at intersection
		lanes LaneList,
		-- Lanes belong to this link
		...
		}
	
	--DF_LinkList
	LinkList ::= SEQUENCE (SIZE(1..32)) OF Link
	
	--DF_MotionConfidenceSet
	MotionConfidenceSet ::= SEQUENCE {
		speedCfd SpeedConfidence OPTIONAL,
		headingCfd HeadingConfidence OPTIONAL,
		steerCfd SteeringWheelAngleConfidence OPTIONAL
		}
	
	--DF_Movement
	Movement ::=SEQUENCE{
		remoteIntersection NodeReferenceID,
		-- This entry indicates the downstream intersection of the link this lane connects to
		-- This provides a means to create meshed of lanes
		phaseId PhaseID OPTIONAL
		-- The matching signal group send by
		-- the SPAT message for this lane/maneuver
		-- Shall be present unless the connectingLane
		-- has no signal group (is un-signalized)
		}
	
	--DF_MovementList
	MovementList  ::=SEQUENCE(SIZE(1..32)) OF Movement
	
	--DF_Node
	Node ::= SEQUENCE {
		-- Node can be an intersection, or a road endpoint
		name DescriptiveName OPTIONAL,
		-- Node name
		id NodeReferenceID,
		-- A globally unique value set,
		-- consisting of a regionID and
		-- node ID assignment
		refPos Position3D,
		-- 3D position of the center of this Node.
		-- This position is also the reference position for the elements inside
		inLinks LinkList OPTIONAL,
		-- all the links enter this Node
		...
		}
	
	--DF_NodeList
	NodeList ::= SEQUENCE (SIZE(1..32)) OF Node

	--DF_NodeReferenceID
	NodeReferenceID ::= SEQUENCE {
		region RoadRegulatorID OPTIONAL,
		-- a globally unique regional assignment value
		-- typical assigned to a regional DOT authority
		-- the value zero shall be used for testing needs
		id NodeID
		-- a unique mapping to the node
		-- in question within the above region of use
		}
	
	--DF_ParticipantData
	ParticipantData ::= SEQUENCE {
		ptcType ParticipantType,
		ptcId INTEGER (0..65535),
		-- temporary ID set by RSU
		-- 0 is RSU itself
		-- 1..65535 represent participants detected by RSU
		source SourceType,
		id OCTET STRING (SIZE(8)) OPTIONAL,
		plateNo OCTET STRING (SIZE(16)) OPTIONAL,
		secMark DSecond,
		pos PositionOffsetLLV,
		accuracy PositionConfidenceSet,
		transmission TransmissionState OPTIONAL,
		speed Speed,
		heading Heading,
		angle SteeringWheelAngle OPTIONAL,
		motionCfd MotionConfidenceSet OPTIONAL,
		accelSet AccelerationSet4Way OPTIONAL,
		size VehicleSize,
		vehicleClass VehicleClassification OPTIONAL,
		...
		}
	
	--DF_ParticipantList
	ParticipantList ::=SEQUENCE(SIZE(1..16)) OF ParticipantData
	
	--DF_PathHistory
	PathHistory ::=SEQUENCE{
		initialPosition FullPositionVector OPTIONAL,
		currGNSSstatus GNSSstatus OPTIONAL,
		crumbData PathHistoryPointList,
		...
		}
	
	--DF_PathHistoryPoint
	PathHistoryPoint ::=SEQUENCE{
		llvOffset PositionOffsetLLV,
		timeOffset TimeOffset,
		-- Offset backwards in time
		speed Speed OPTIONAL,
		-- Speed over the reported period
		posAccuracy PositionConfidenceSet OPTIONAL,
		-- The accuracy of this value
		heading CoarseHeading OPTIONAL,
		-- overall heading
		...
		}
	
	-- DF_PathHistoryPointList
	PathHistoryPointList ::=SEQUENCE(SIZE(1..23)) OF PathHistoryPoint
	
	-- DF_PathPointList
	PathPointList ::=SEQUENCE(SIZE(2..32)) OF PositionOffsetLLV
	
	-- DF_PathPrediction
	PathPrediction ::=SEQUENCE{
		radiusOfCurve RadiusOfCurvature,
		-- LSB units of 10cm
		-- straight path to use value of 32767
		confidence Confidence,
		-- LSB units of 0.5 present
		...
		}
	
	-- DF_Phase
	Phase ::= SEQUENCE{
		id PhaseID,
		-- the group id is used to map to lists
		-- of lanes (and their descriptions)
		-- which this MovementState data applies to
		-- see comments in the Remarks for usage details
		phaseStates PhaseStateList
		-- Consisting of sets of movement data with:
		-- a) SignalPhaseState
		-- b) TimeChangeDetails, and
		-- c) AdvisorySpeeds (optional )
		-- Note one or more of the movement events may be for
		-- a future time and that this allows conveying multiple
		-- predictive phase and movement timing for various uses
		-- for the current signal group
		}
	
	-- DF_PhaseList
	PhaseList ::= SEQUENCE (SIZE(1..16)) OF Phase
	-- List of phases in one traffic signal
	
	--DF_PhaseState
	PhaseState ::= SEQUENCE {
		light LightState,
		-- Consisting of:
		-- Phase state (the basic 11 states)
		-- Directional, protected, or permissive state
		timing TimeChangeDetails OPTIONAL,
		-- Timing Data in UTC time stamps for event
		-- includes start and min/max end times of phase
		-- confidence and estimated next occurrence
		...
		}
	
	-- DF_PhaseStateList
	PhaseStateList ::= SEQUENCE (SIZE(1..16)) OF PhaseState
	
	--DF_PointList
	PointList ::=SEQUENCE(SIZE(2..31)) OF RoadPoint	
	-- At least 2 pints of 1 lane
	-- entry line and exit line
	-- points need to be listed sequatially
	-- from upstream to downstream
	
	-- DF_Position-LL-24B
	Position-LL-24B ::= SEQUENCE {
		-- ranges of +- 0.0002047 degrees
		-- ranges of +- 22.634554 meters at the equator
		lon OffsetLL-B12,
		lat OffsetLL-B12
		}
		
	-- DF_Position-LL-28B	
	Position-LL-28B ::= SEQUENCE {
		-- ranges of +- 0.0008191 degrees
		-- ranges of +- 90.571389 meters at the equator
		lon OffsetLL-B14,
		lat OffsetLL-B14
		}	
	
	-- DF_Position-LL-32B
	Position-LL-32B ::= SEQUENCE {
		-- ranges of +- 0.0032767 degrees
		-- ranges of +- 362.31873 meters at the equator
		lon OffsetLL-B16,
		lat OffsetLL-B16
		}
		
	-- DF_Position-LL-36B	
	Position-LL-36B ::= SEQUENCE{
		-- ranges of +- 0.0131071 degrees
		-- ranges of +- 01.449308 Kmeters at the equator
		lon OffsetLL-B18,
		lat OffsetLL-B18
		}
	
	-- DF_Position-LL-44B	
	Position-LL-44B ::= SEQUENCE{
		-- ranges of +- 0.02097151 degrees
		-- ranges of +- 23.189096 Kmeters at the equator
		lon OffsetLL-B22,
		lat OffsetLL-B22
		}
		
	-- DF_Position-LL-48B	
	Position-LL-48B ::= SEQUENCE{
		-- ranges of +- 0.8388607 degrees
		-- ranges of +- 92.756481 Kmeters at the equator
		lon OffsetLL-B24,
		lat OffsetLL-B24
		}

	-- DF_Position-LLmD-64b
	Position-LLmD-64b ::= SEQUENCE{
		-- a full 32b Lat/Lon range
		lon Longitude,
		lat Latitude
		}		
	
	-- DF_Position3D
	Position3D ::= SEQUENCE {
		lat Latitude, 
		-- in 1/10th micro degrees
		long Longitude, 
		-- in 1/10th micro degrees
		elevation Elevation OPTIONAL, 
		-- in 10 cm units
		...
		}
	
	-- DF_PositionConfidenceSet
	PositionConfidenceSet ::= SEQUENCE {
		pos PositionConfidence, -- for both horizontal directions
		elevation ElevationConfidence OPTIONAL
		}
	
	-- DF_PositionOffsetLL
	PositionOffsetLL ::=CHOICE{
		-- Locations with LL content Span at the equator when using a zoom of one:
		position-LL1 Position-LL-24B,
		-- within +- 22.634554 meters of the reference position
		position-LL2 Position-LL-28B,
		-- within +- 90.571389 meters of the reference position
		position-LL3 Position-LL-32B,
		-- within +- 362.31873 meters of the reference position
		position-LL4 Position-LL-36B,
		-- within +- 01.449308 Kmeters of the reference position
		position-LL5 Position-LL-44B,
		-- within +- 23.189096 Kmeters of the reference position
		position-LL6 Position-LL-48B,
		-- within +- 92.756481 Kmeters of the reference position
		position-LatLon Position-LLmD-64b
		-- node is a full 32b Lat/Lon range
		}
	
	-- DF_PositionOffsetLLV
	PositionOffsetLLV ::= SEQUENCE {
		offsetLL PositionOffsetLL,
		-- offset in lon/lat
		offsetV VerticalOffset OPTIONAL
		-- offset in elevation
		}
		
	--DF_RegulatorySpeedLimit	
	RegulatorySpeedLimit ::= SEQUENCE {
		type SpeedLimitType,
		-- The type of regulatory speed which follows
		speed Speed
		-- The speed in units of 0.02 m/s
		-- See Section 11 for converting and translating
		-- speed expressed in mph into units of m/s
		}
		
	--DF_RoadPoint
	RoadPoint ::= SEQUENCE {
		posOffset PositionOffsetLLV,
		-- Position offset to the reference position
		...
		}
	
	--DF_SignalState
	SignalState ::= SEQUENCE {
		status IntersectionStatusObject,
		-- general status of the controller(s)
		moy MinuteOfTheYear OPTIONAL,
		-- Minute of current UTC year
		-- used only with messages to be archived
		timeStamp DSecond OPTIONAL,
		-- the mSec point in the current UTC minute that
		-- this message was constructed
		phases PhaseList
		-- Each Movement is given in turn
		-- and contains its signal phase state,
		-- mapping to the lanes it applies to, and
		-- point in time it will end, and it
		-- may contain both active and future states
		}	
	
	--DF_SpeedLimitList
	SpeedLimitList ::= SEQUENCE (SIZE(1..9)) OF RegulatorySpeedLimit
	
	--DF_TimeChangeDetails
	TimeChangeDetails ::=SEQUENCE{
		startTime TimeMark,
		-- When this phase state started,
		-- if already started, the valie is 0
		minEndTime TimeMark OPTIONAL,
		-- Expected shortest end time
		-- if already started, the value is the min left time from now 
		-- if not started, the value means the min length of this phase
		maxEndTime TimeMark OPTIONAL,
		-- Expected longest end time
		-- if already started, the value is the max left time from now
		-- if not started, the value means the max length of this phase
		likelyEndTime TimeMark,
		-- Best predicted value based on the data
		-- if already started, the value is the likely left time from now
		-- if not started, the value means the likely the length of this phase
		timeConfidence Confidence OPTIONAL,
		-- Confidence of likelyTime
		nextStartTime TimeMark OPTIONAL,
		-- A rough estimate of time when this phase state may next occur again
		-- after the above endTime
		-- used to support various ECO drivint power management needs.
		-- If already started, this value is recommended to be delivered.
		nextDuration TimeMark OPTIONAL
		-- A rough estimate of the time length of this phase state
		-- when it may next occur again after the above endTime
		-- used to support various ECO drivint power management needs.
		-- If already started, this value is recommended to be delivered.
		}
	
	--DF_VehicleClassification
	VehicleClassification ::= SEQUENCE {
		classification BasicVehicleClass,
		...
		}
	
	--DF_VehicleSafetyExtensions
	VehicleSafetyExtensions ::=SEQUENCE{
		event VehicleEventFlags OPTIONAL,
		pathHistory PathHistory OPTIONAL,
		pathPrediction PathPrediction OPTIONAL,
		lights ExteriorLights OPTIONAL,
		...
		}
	
	--DF_VehicleSize
	VehicleSize ::= SEQUENCE {
		width VehicleWidth,
		length VehicleLength,
		height VehicleHeight OPTIONAL
		}
	
	--DF_VerticalOffset
	VerticalOffset ::= CHOICE {
		-- Vertical Offset
		-- All below in steps of 10cm above or below the reference ellipsoid
		offset1 VertOffset-B07, -- with a range of +- 6.3 meters vertical
		offset2 VertOffset-B08, -- with a range of +- 12.7 meters vertical
		offset3 VertOffset-B09, -- with a range of +- 25.5 meters vertical
		offset4 VertOffset-B10, -- with a range of +- 51.1 meters vertical
		offset5 VertOffset-B11, -- with a range of +- 102.3 meters vertical
		offset6 VertOffset-B12, -- with a range of +- 204.7 meters vertical
		elevation Elevation -- with a range of -409.5 to + 6143.9 meters
		}
		
	--DE_Acceleration
	Acceleration ::= INTEGER (-2000..2001)
	-- LSB units are 0.01 m/s^2
	-- the value 2000 shall be used for values greater than 2000
	-- the value -2000 shall be used for values less than -2000
	-- a value of 2001 shall be used for Unavailable
		
	--DE_AlertType
	AlertType ::= INTEGER (0..65535)
		-- Text message warning = 0
		-- Traffic signs according to China GB5768
		-- Danger = 37
		-- Rockfall = 15
		-- SharpTurn = 2
		-- UnderConstruction = 38
		-- Slippy = 17
		-- Tunnel = 21
	
	--DE_AllowedManeuvers
	AllowedManeuvers ::= BIT STRING {
		-- With bits as defined:
		-- Allowed maneuvers at path end (stop line)
		-- All maneuvers with bits not set are therefore prohibited
		-- A value of zero shall be used for unknown, indicating no Maneuver
		maneuverStraightAllowed (0),
		-- a Straight movement is allowed in this lane
		maneuverLeftAllowed (1),
		-- a Left Turn movement is allowed in this lane
		maneuverRightAllowed (2),
		-- a Right Turn movement is allowed in this lane
		maneuverUTurnAllowed (3),	
		-- a U turn movement is allowed in this lane
		maneuverLeftTurnOnRedAllowed (4),
		-- a Stop, and then proceed when safe movement
		-- is allowed in this lane
		maneuverRightTurnOnRedAllowed (5),
		-- a Stop, and then proceed when safe movement
		-- is allowed in this lane
		maneuverLaneChangeAllowed (6),
		-- a movement which changes to an outer lane
		-- on the egress side is allowed in this lane
		-- (example: left into either outbound lane)
		maneuverNoStoppingAllowed (7),
		-- the vehicle should not stop at the stop line
		-- (example: a flashing green arrow)
		yieldAllwaysRequired (8),
		-- the allowed movements above are not protected
		-- (example: an permanent yellow condition)
		goWithHalt (9),
		-- after making a full stop, may proceed
		caution (10),
		-- proceed past stop line with caution
		reserved1 (11)
		-- used to align to 12 Bit Field
		} (SIZE(12))
	
	--DE_AntiLockBrakeStatus
	AntiLockBrakeStatus ::= ENUMERATED {
		unavailable (0), -- B'00 Vehicle Not Equipped with ABS Brakes
		-- or ABS Brakes status is unavailable
		off (1), -- B'01 Vehicle's ABS are Off
		on (2), -- B'10 Vehicle's ABS are On ( but not Engaged )
		engaged (3) -- B'11 Vehicle's ABS control is Engaged on any wheel
		}	
		
	--DE_AuxiliaryBrakeStatus
	AuxiliaryBrakeStatus ::= ENUMERATED {
		unavailable (0), -- B'00 Vehicle Not Equipped with Aux Brakes
		-- or Aux Brakes status is unavailable
		off (1), -- B'01 Vehicle's Aux Brakes are Off
		on (2), -- B'10 Vehicle's Aux Brakes are On(Engaged)
		reserved (3) --B'11
		}
		
	--DE_BasicVehicleClass
	BasicVehicleClass ::= INTEGER(0..255)
	unknownVehicleClass BasicVehicleClass ::= 0
	-- Not Equipped, Not known or unavailable
	specialVehicleClass BasicVehicleClass ::= 1
	-- Special use
	--
	-- Basic Passenger Motor Vehicle Types
	--
	passenger-Vehicle-TypeUnknown BasicVehicleClass ::= 10 -- default type
	passenger-Vehicle-TypeOther BasicVehicleClass ::= 11
	-- various fuel types are handled in another element
	--
	-- Light Trucks, Pickup, Van, Panel
	--
	lightTruck-Vehicle-TypeUnknown BasicVehicleClass ::= 20 -- default type
	lightTruck-Vehicle-TypeOther BasicVehicleClass ::= 21
	--
	-- Trucks, Various axle types, includes HPMS items
	--
	truck-Vehicle-TypeUnknown BasicVehicleClass ::= 25 -- default type
	truck-Vehicle-TypeOther BasicVehicleClass ::= 26
	truck-axleCnt2 BasicVehicleClass ::= 27 -- Two axle, six tire single units
	truck-axleCnt3 BasicVehicleClass ::= 28 -- Three axle, single units
	truck-axleCnt4 BasicVehicleClass ::= 29 -- Four or more axle, single unit
	truck-axleCnt4Trailer BasicVehicleClass ::= 30 -- Four or less axle, single trailer
	truck-axleCnt5Trailer BasicVehicleClass ::= 31 -- Five or less axle, single trailer
	truck-axleCnt6Trailer BasicVehicleClass ::= 32 -- Six or more axle, single trailer
	truck-axleCnt5MultiTrailer BasicVehicleClass ::= 33 -- Five or less axle, multi-trailer
	truck-axleCnt6MultiTrailer BasicVehicleClass ::= 34 -- Six axle, multi-trailer
	truck-axleCnt7MultiTrailer BasicVehicleClass ::= 35 -- Seven or more axle, multi-trailer
	--
	-- Motorcycle Types
	--
	
	motorcycle-TypeUnknown BasicVehicleClass ::= 40 -- default type
	motorcycle-TypeOther BasicVehicleClass ::= 41
	motorcycle-Cruiser-Standard BasicVehicleClass ::= 42
	motorcycle-SportUnclad BasicVehicleClass ::= 43
	motorcycle-SportTouring BasicVehicleClass ::= 44
	motorcycle-SuperSport BasicVehicleClass ::= 45
	motorcycle-Touring BasicVehicleClass ::= 46
	motorcycle-Trike BasicVehicleClass ::= 47
	motorcycle-wPassengers BasicVehicleClass ::= 48 -- type not stated
	--
	-- Transit Types
	--
	transit-TypeUnknown BasicVehicleClass ::= 50 -- default type
	transit-TypeOther BasicVehicleClass ::= 51
	transit-BRT BasicVehicleClass ::= 52
	transit-ExpressBus BasicVehicleClass ::= 53
	transit-LocalBus BasicVehicleClass ::= 54
	transit-SchoolBus BasicVehicleClass ::= 55
	transit-FixedGuideway BasicVehicleClass ::= 56
	transit-Paratransit BasicVehicleClass ::= 57
	transit-Paratransit-Ambulance BasicVehicleClass ::= 58
	--
	-- Emergency Vehicle Types
	--
	emergency-TypeUnknown BasicVehicleClass ::= 60 -- default type
	emergency-TypeOther BasicVehicleClass ::= 61 -- includes federal users
	emergency-Fire-Light-Vehicle BasicVehicleClass ::= 62
	emergency-Fire-Heavy-Vehicle BasicVehicleClass ::= 63
	emergency-Fire-Paramedic-Vehicle BasicVehicleClass ::= 64
	emergency-Fire-Ambulance-Vehicle BasicVehicleClass ::= 65
	emergency-Police-Light-Vehicle BasicVehicleClass ::= 66
	emergency-Police-Heavy-Vehicle BasicVehicleClass ::= 67
	emergency-Other-Responder BasicVehicleClass ::= 68
	emergency-Other-Ambulance BasicVehicleClass ::= 69
	--
	-- Other DSRC Equipped Travelers
	--
	otherTraveler-TypeUnknown BasicVehicleClass ::= 80 -- default type
	otherTraveler-TypeOther BasicVehicleClass ::= 81
	otherTraveler-Pedestrian BasicVehicleClass ::= 82
	otherTraveler-Visually-Disabled BasicVehicleClass ::= 83
	otherTraveler-Physically-Disabled BasicVehicleClass ::= 84
	otherTraveler-Bicycle BasicVehicleClass ::= 85
	otherTraveler-Vulnerable-Roadworker BasicVehicleClass ::= 86
	--
	-- Other DSRC Equipped Device Types
	--
	infrastructure-TypeUnknown BasicVehicleClass ::= 90 -- default type
	infrastructure-Fixed BasicVehicleClass ::= 91
	infrastructure-Movable BasicVehicleClass ::= 92
	equipped-CargoTrailer BasicVehicleClass ::= 93
		
	--DE_BrakeAppliedStatus	
	BrakeAppliedStatus ::= BIT STRING {
		unavailable (0), -- When set, the brake applied status is unavailable
		leftFront (1), -- Left Front Active
		leftRear (2), -- Left Rear Active
		rightFront (3), -- Right Front Active
		rightRear (4) -- Right Rear Active
		} (SIZE (5))
	
	--DE_BrakeBoostApplied
	BrakeBoostApplied ::= ENUMERATED {
		unavailable (0), -- Vehicle not equipped with brake boost
		-- or brake boost data is unavailable
		off (1), -- Vehicle's brake boost is off
		on (2) -- Vehicle's brake boost is on (applied)
		}
	
	--DE_BrakePedalStatus
	BrakePedalStatus ::= ENUMERATED {
		unavailable (0), -- Vehicle brake pedal detector is unavailable
		off (1), -- Vehicle's brake padel is not pressed
		on (2) -- Vehicle's brake padel is pressed
		}
	
	--DE_CoarseHeading
	CoarseHeading ::= INTEGER (0..240)
		-- Where the LSB is in units of 1.5 degrees
		-- over a range of 0 ～ 358.5 degrees
		-- the value 240 shall be used for unavailable
	
	--DE_Confidence
	Confidence ::= INTEGER (0..200)
	-- LSB units of 0.5 percent
	
	--DE_DDay
	DDay ::= INTEGER (0..31)
	-- units of days
	
	--DE_DescriptiveName
	DescriptiveName ::= IA5String (SIZE(1..63))
	
	--DE_DHour
	DHour ::= INTEGER (0..31)
	-- units of hours
	
	--DE_DMinute
	DMinute ::= INTEGER (0..60)
	-- units of minutes
	
	--DE_DMonth
	DMonth ::= INTEGER(0..12)
	-- uints of months
	
	--DE_DSecond
	DSecond ::=INTEGER(0..65535)
	-- uints of milliseconds
	
	--DE_DTimeOffset
	DTimeOffset ::= INTEGER(-840..840)
	-- uints of minutes from UTC time
	
	--DE_DYear
	DYear ::= INTEGER(0..4095)
	-- uints of years
	
	--DE_Elevation
	Elevation ::=INTEGER(-4096..61439)
	-- In units of 10 cm steps above or blow the reference ellipsoid
	-- Providing a range of -409.5 to + 6143.9 meters
	-- The value -4096 shall be used when Unknown is to be sent
	
	--DE_ElevationConfidence
	ElevationConfidence ::= ENUMERATED {
		unavailable (0), -- B'0000 Not Equipped or unavailable
		elev-500-00 (1), -- B'0001 (500 m)
		elev-200-00 (2), -- B'0010 (200 m)
		elev-100-00 (3), -- B'0011 (100 m)
		elev-050-00 (4), -- B'0100 (50 m)
		elev-020-00 (5), -- B'0101 (20 m)
		elev-010-00 (6), -- B'0110 (10 m)
		elev-005-00 (7), -- B'0111 (5 m)
		elev-002-00 (8), -- B'1000 (2 m)
		elev-001-00 (9), -- B'1001 (1 m)
		elev-000-50 (10), -- B'1010 (50 cm)
		elev-000-20 (11), -- B'1011 (20 cm)
		elev-000-10 (12), -- B'1100 (10 cm)
		elev-000-05 (13), -- B'1101 (5 cm)
		elev-000-02 (14), -- B'1110 (2 cm)
		elev-000-01 (15) -- B'1111 (1 cm)
		} -- Encoded as a 4 bit value
	
	--DE_ExteriorLights
	ExteriorLights ::= BIT STRING {
		-- All lights off is indicated by no bits set
		lowBeamHeadlightsOn (0),
		highBeamHeadlightsOn (1),
		leftTurnSignalOn (2),
		rightTurnSignalOn (3),
		hazardSignalOn (4),
		automaticLightControlOn (5),
		daytimeRunningLightsOn (6),
		fogLightOn (7),
		parkingLightsOn (8)
		} (SIZE (9, ...))
	
	--DE_GNSSstatus
	GNSSstatus ::= BIT STRING {
		unavailable (0), -- Not Equipped or unavailable
		isHealthy (1),
		isMonitored (2),
		baseStationType (3), -- Set to zero if a moving base station,
		-- or if a rover device (an OBU),
		-- set to one if it is a fixed base station
		aPDOPofUnder5 (4), -- A dilution of precision greater than 5
		inViewOfUnder5 (5), -- Less than 5 satellites in view
		localCorrectionsPresent (6), -- DGPS type corrections used
		networkCorrectionsPresent (7) -- RTK type corrections used
		} (SIZE(8))
		
	--DE_Heading	
	Heading ::= INTEGER (0..28800)
	-- LSB of 0.0125 degrees
	-- A range of 0 to 359.9875 degrees
	
	--DE_HeadingConfidence
	HeadingConfidence ::= ENUMERATED {
		unavailable (0), -- B'000 Not Equipped or unavailable
		prec10deg (1), -- B'010 10 degrees
		prec05deg (2), -- B'011 5 degrees
		prec01deg (3), -- B'100 1 degrees
		prec0-1deg (4), -- B'101 0.1 degrees
		prec0-05deg (5), -- B'110 0.05 degrees
		prec0-01deg (6), -- B'110 0.01 degrees
		prec0-0125deg (7) -- B'111 0.0125 degrees, aligned with heading LSB
		} -- Encoded as a 3 bit value
	
	--DE_IntersectionStatusObject
	IntersectionStatusObject ::= BIT STRING {
		manualControlIsEnabled (0),
		-- Timing reported is per programmed values, etc. but person
		-- at cabinet can manually request that certain intervals are
		-- terminated early (e.g. green).
		stopTimeIsActivated (1),
		-- And all counting/timing has stopped.
		failureFlash (2),
		-- Above to be used for any detected hardware failures,
		-- e.g. conflict monitor as well as for police flash
		preemptIsActive (3),
		signalPriorityIsActive (4),
		-- Additional states
		fixedTimeOperation (5),
		-- Schedule of signals is based on time only
		-- (i.e. the state can be calculated)
		trafficDependentOperation (6),
		-- Operation is based on different levels of traffic parameters
		-- (requests, duration of gaps or more complex parameters)
		standbyOperation (7),
		-- Controller: partially switched off or partially amber flashing
		failureMode (8),
		-- Controller has a problem or failure in operation
		off (9),
		-- Controller is switched off
		-- Related to MAP and SPAT bindings
		recentMAPmessageUpdate (10),
		-- Map revision with content changes
		recentChangeInMAPassignedLanesIDsUsed (11),
		-- Change in MAP's assigned lanes used (lane changes)
		-- Changes in the active lane list description
		noValidMAPisAvailableAtThisTime (12),
		-- MAP (and various lanes indexes) not available
		noValidSPATisAvailableAtThisTime (13)
		-- SPAT system is not working at this time
		-- Bits 14,15 reserved at this time and shall be zero
		} (SIZE(16))	
		
	--DE_LaneAttributes-Barrier
	LaneAttributes-Barrier ::= BIT STRING {
		-- With bits as defined:
		median-RevocableLane (0),
		-- this lane may be activated or not based
		-- on the current SPAT message contents
		-- if not asserted, the lane is ALWAYS present
		median (1),
		whiteLineHashing (2),	
		stripedLines (3),
		doubleStripedLines (4),
		trafficCones (5),
		constructionBarrier (6),
		trafficChannels (7),
		lowCurbs (8),
		highCurbs (9) --Bits 10~15 reserved and set to zero
	}(SIZE(16))
		
	--DE_LaneAttributes-Bike
	LaneAttributes-Bike ::= BIT STRING { -- With bits as defined:
		bikeRevocableLane (0),
		-- this lane may be activated or not based
		-- on the current SPAT message contents
		-- if not asserted, the lane is ALWAYS present
		pedestrianUseAllowed (1),
		-- The path allows pedestrian traffic,
		-- if not set, this mode is prohibited
		isBikeFlyOverLane (2),
		-- path of lane is not at grade
		fixedCycleTime (3),
		-- the phases use preset times
		-- i.e. there is not a 'push to cross' button
		biDirectionalCycleTimes (4),
		-- ped walk phases use different SignalGroupID
		-- for each direction. The first SignalGroupID
		-- in the first Connection represents 'inbound'
		-- flow (the direction of travel towards the first
		-- node point) while second SignalGroupID in the
		-- next Connection entry represents the 'outbound'
		-- flow. And use of RestrictionClassID entries
		-- in the Connect follow this same pattern in pairs.
		isolatedByBarrier (5),
		unsignalizedSegmentsPresent (6)
		-- The lane path consists of one of more segments
		-- which are not part of a signal group ID
		-- Bits 7~15 reserved and set to zero
		} (SIZE (16))			
		
	--DE_LaneAttributes-Crosswalk
	LaneAttributes-Crosswalk ::= BIT STRING {
		-- With bits as defined:
		-- MUTCD provides no suitable "types" to use here
		crosswalkRevocableLane (0),
		-- this lane may be activated or not based
		-- on the current SPAT message contents
		-- if not asserted, the lane is ALWAYS present
		bicyleUseAllowed (1),
		-- The path allows bicycle traffic,
		-- if not set, this mode is prohibited
		isXwalkFlyOverLane (2),
		-- path of lane is not at grade
		fixedCycleTime (3),
		-- ped walk phases use preset times
		-- i.e. there is not a 'push to cross' button
		biDirectionalCycleTimes (4),
		-- ped walk phases use different SignalGroupID
		-- for each direction. The first SignalGroupID
		-- in the first Connection represents 'inbound'
		-- flow (the direction of travel towards the first
		-- node point) while second SignalGroupID in the
		-- next Connection entry represents the 'outbound'
		-- flow. And use of RestrictionClassID entries
		-- in the Connect follow this same pattern in pairs.
		hasPushToWalkButton (5),
		-- Has a demand input
		audioSupport (6),
		-- audio crossing cues present
		rfSignalRequestPresent (7),
		-- Supports RF push to walk technologies
		unsignalizedSegmentsPresent (8)
		-- The lane path consists of one of more segments
		-- which are not part of a signal group ID
		-- Bits 9~15 reserved and set to zero
	} (SIZE (16))
	
	--DE_LaneAttributes-Parking
	LaneAttributes-Parking ::= BIT STRING {
		-- With bits as defined:
		-- Parking use details, note that detailed restrictions such as
		-- allowed hours are sent by way of ITIS codes in the TIM message
		parkingRevocableLane (0),
		-- this lane may be activated or not based
		-- on the current SPAT message contents
		-- if not asserted, the lane is ALWAYS present
		parallelParkingInUse (1),
		headInParkingInUse (2),
		doNotParkZone (3),
		-- used to denote fire hydrants as well as
		-- short disruptions in a parking zone
		parkingForBusUse (4),
		parkingForTaxiUse (5),
		noPublicParkingUse (6)
		-- private parking, as in front of
		-- private property
		-- Bits 7~15 reserved and set to zero
		} (SIZE (16))
		
	--DE_LaneAttributes-Sidewalk
	LaneAttributes-Sidewalk ::= BIT STRING { -- With bits as defined:
		sidewalk-RevocableLane (0),
		-- this lane may be activated or not based
		-- on the current SPAT message contents
		-- if not asserted, the lane is ALWAYS present
		bicyleUseAllowed (1),
		-- The path allows bicycle traffic,
		-- if not set, this mode is prohibited
		isSidewalkFlyOverLane (2),
		-- path of lane is not at grade
		walkBikes (3)
		-- bike traffic must dismount and walk
		-- Bits 4~15 reserved and set to zero
		} (SIZE (16))
	
	--DE_LaneAttributes-Striping
	LaneAttributes-Striping ::= BIT STRING {
		-- With bits as defined:
		stripeToConnectingLanesRevocableLane (0),
		-- this lane may be activated or not activated based
		-- on the current SPAT message contents
		-- if not asserted, the lane is ALWAYS present
		stripeDrawOnLeft (1),
		stripeDrawOnRight (2),
		-- which side of lane to mark
		stripeToConnectingLanesLeft (3),
		stripeToConnectingLanesRight (4),
		stripeToConnectingLanesAhead (5)
		-- the stripe type should be
		-- presented to the user visually
		-- to reflect stripes in the
		-- intersection for the type of
		-- movement indicated
		-- Bits 6~15 reserved and set to zero
		} (SIZE (16))	
		
	--DE_LaneAttributes-TrackedVehicle
	LaneAttributes-TrackedVehicle ::= BIT STRING {
		-- With bits as defined:
		spec-RevocableLane (0),
		-- this lane may be activated or not based
		-- on the current SPAT message contents
		-- if not asserted, the lane is ALWAYS present
		spec-commuterRailRoadTrack (1),
		spec-lightRailRoadTrack (2),
		spec-heavyRailRoadTrack (3),
		spec-otherRailType (4) -- Bits 5~15 reserved and set to zero
		} (SIZE (16))
	
	--DE_LaneAttributes-Vehicle
	LaneAttributes-Vehicle ::= BIT STRING {
		-- With bits as defined:
		isVehicleRevocableLane (0),
		-- this lane may be activated or not based
		-- on the current SPAT message contents
		-- if not asserted, the lane is ALWAYS present
		isVehicleFlyOverLane (1),
		-- path of lane is not at grade
		hovLaneUseOnly (2),
		restrictedToBusUse (3),
		restrictedToTaxiUse (4),
		restrictedFromPublicUse (5),
		hasIRbeaconCoverage (6),
		permissionOnRequest (7) -- e.g. to inform about a lane for e-cars
		} (SIZE (8,...))
				
	--DE_LaneID		
	LaneID ::= INTEGER (0..255)
		-- the value 0 shall be used when the lane ID is
		-- not available or not known
		-- the value 255 is reserved for future use

	--DE_LaneSharing
	LaneSharing ::= BIT STRING {
		-- With bits as defined:
		overlappingLaneDescriptionProvided (0),
		-- Assert when another lane object is present to describe the
		-- path of the overlapping shared lane
		-- this construct is not used for lane objects which simply cross
		multipleLanesTreatedAsOneLane (1),
		-- Assert if the lane object path and width details represents
		-- multiple lanes within it that are not further described
		-- Various modes and type of traffic that may share this lane:
		otherNonMotorizedTrafficTypes (2), -- horse drawn etc.
		individualMotorizedVehicleTraffic (3),
		busVehicleTraffic (4),
		taxiVehicleTraffic (5),
		pedestriansTraffic (6),
		cyclistVehicleTraffic (7),
		trackedVehicleTraffic (8),
		pedestrianTraffic (9)
		} (SIZE (10))
		-- All zeros would indicate 'not shared' and 'not overlapping'
	
	--DE_LaneWidth
	LaneWidth ::= INTEGER (0..32767)
	-- units of 1 cm
	
	--DE_Latitude
	Latitude ::= INTEGER (-900000000..900000001)
	-- LSB = 1/10 micro degree
	-- Providing a range of plus-minus 90 degrees
	
	--DE_LightState
	LightState ::= ENUMERATED {
		-- Note that based on the regions and the operating mode not every
		-- phase will be used in all transportation modes and that not
		-- every phase will be used in all transportation modes
		unavailable (0),
		-- This state is used for unknown or error
		dark (1),
		-- The signal head is dark (unlit)
		-- Reds
		stop-Then-Proceed (2),
		-- Often called 'flashing red' in US
		-- Driver Action:
		-- Stop vehicle at stop line.
		-- Do not proceed unless it is safe.
		-- Note that the right to proceed either right or left when
		-- it is safe may be contained in the lane description to
		-- handle what is called a 'right on red'
		stop-And-Remain (3),
		-- e.g. called 'red light' in US
		-- Driver Action:
		-- Stop vehicle at stop line.
		-- Do not proceed.
		-- Note that the right to proceed either right or left when
		-- it is safe may be contained in the lane description to
		-- handle what is called a 'right on red'
		-- Greens
		pre-Movement (4),
		-- Not used in the US, red+yellow partly in EU
		-- Driver Action:
		-- Stop vehicle.
		-- Prepare to proceed (pending green)
		-- (Prepare for transition to green/go)
		permissive-Movement-Allowed (5),
		-- Often called 'permissive green' in US
		-- Driver Action:
		-- Proceed with caution,
		-- must yield to all conflicting traffic
		-- Conflicting traffic may be present
		-- in the intersection conflict area
		protected-Movement-Allowed (6),
		-- Often called 'protected green' in US
		-- Driver Action:
		-- Proceed, tossing caution to the wind,
		-- in indicated (allowed) direction.
		-- Yellows / Ambers
		-- The vehicle is not allowed to cross the stop bar if it is possible
		-- to stop without danger.
		intersection-clearance (7),
		-- Often called 'permissive yellow' in US
		-- Driver Action:
		-- Prepare to stop.
		-- Proceed if unable to stop,
		-- Clear Intersection.
		-- Conflicting traffic may be present
		-- in the intersection conflict area
		caution-Conflicting-Traffic (8)
		-- Often called 'flashing yellow' in US
		-- Often used for extended periods of time
		-- Driver Action:
		-- Proceed with caution,
		-- Conflicting traffic may be present
		-- in the intersection conflict area
		}
		-- The above number assignments are not used with UPER encoding
		-- and are only to be used with DER or implicit encoding	

	--DE_Longitude
	Longitude ::= INTEGER (-1799999999..1800000001)
	-- LSB = 1/10 micro degree
	-- Providing a range of plus-minus 180 degrees
	
	--DE_MinuteOfTheYear
	MinuteOfTheYear ::= INTEGER (0..527040)
	-- the value 527040 shall be used for invalid
	
	--DE_MsgCount
	MsgCount ::= INTEGER (0..127)
	
	--DE_NodeID
	NodeID ::= INTEGER (0..65535)
	-- The values zero through 255 are allocated for testing purposes
	-- Note that the value assigned to a node will be
	-- unique within a given regional ID only
	
	
	--DE_OffsetLL-B12
	OffsetLL-B12 ::= INTEGER (-2048..2047)
	-- A range of +- 0.0002047 degrees
	-- In LSB units of 0.1 microdegrees
	
	--DE_OffsetLL-B14
	OffsetLL-B14 ::= INTEGER (-8192..8191)
	-- A range of +- 0.0008191 degrees
	-- In LSB units of 0.1 microdegrees
	
	--DE_OffsetLL-B16
	OffsetLL-B16 ::= INTEGER (-32768..32767)
	-- A range of +- 0.0032767 degrees
	-- In LSB units of 0.1 microdegrees
	
	--DE_OffsetLL-B18
	OffsetLL-B18 ::= INTEGER (-131072..131071)
	-- A range of +- 0.0131071 degrees
	-- The value +131071 shall be used for values >= than +0.0131071 degrees
	-- The value -131071 shall be used for values <= than -0.0131071 degrees
	-- The value -131072 shall be used unknown
	-- In LSB units of 0.1 microdegrees
	
	--DE_OffsetLL-B22
	OffsetLL-B22 ::= INTEGER (-2097152..2097151)
	-- A range of +- 0.2097151 degrees
	-- In LSB units of 0.1 microdegrees
	
	--DE_OffsetLL-B24
	OffsetLL-B24 ::= INTEGER (-8388608..8388607)
	-- A range of +- 0.8388607 degrees
	-- In LSB units of 0.1 microdegrees
	
	--DE_ParticipantType
	ParticipantType ::= ENUMERATED {
		unknown (0), -- B'0000 Unknown
		motor (1), -- B'0001 motor
		non-motor (2), -- B'0010 non-motor
		pedestrian (3), -- B'0011 pedestrian
		rsu (4), -- B'0100 rsu
		...
		} -- Encoded as a 4 bit value
	
	--DE_PhaseID
	PhaseID ::= INTEGER (0..255)
	-- The value 0 shall be used when the ID is
	-- not available or not known
	
	--DE_PositionConfidence
	PositionConfidence ::= ENUMERATED {
		unavailable (0), -- B'0000 Not Equipped or unavailable
		a500m (1), -- B'0001 500m or about 5 * 10 ^ -3 decimal degrees
		a200m (2), -- B'0010 200m or about 2 * 10 ^ -3 decimal degrees
		a100m (3), -- B'0011 100m or about 1 * 10 ^ -3 decimal degrees
		a50m (4), -- B'0100 50m or about 5 * 10 ^ -4 decimal degrees
		a20m (5), -- B'0101 20m or about 2 * 10 ^ -4 decimal degrees
		a10m (6), -- B'0110 10m or about 1 * 10 ^ -4 decimal degrees
		a5m (7), -- B'0111 5m or about 5 * 10 ^ -5 decimal degrees
		a2m (8), -- B'1000 2m or about 2 * 10 ^ -5 decimal degrees
		a1m (9), -- B'1001 1m or about 1 * 10 ^ -5 decimal degrees
		a50cm (10), -- B'1010 0.50m or about 5 * 10 ^ -6 decimal degrees
		a20cm (11), -- B'1011 0.20m or about 2 * 10 ^ -6 decimal degrees
		a10cm (12), -- B'1100 0.10m or about 1 * 10 ^ -6 decimal degrees
		a5cm (13), -- B'1101 0.05m or about 5 * 10 ^ -7 decimal degrees
		a2cm (14), -- B'1110 0.02m or about 2 * 10 ^ -7 decimal degrees
		a1cm (15) -- B'1111 0.01m or about 1 * 10 ^ -7 decimal degrees
		} -- Encoded as a 4 bit value
		
	--DE_Priority
	Priority ::= OCTET STRING (SIZE(1))
	-- The lower five bits are reserved and shall be set to zero
	-- Value from B00000000 to B11100000 represents the lowest to the highest level

	--DE_Radius
	Radius ::= INTEGER (0..1024)
	-- Radius of roadside alert
	-- Unit is 0.1m

	--DE_RadiusOfCurvature
	RadiusOfCurvature ::= INTEGER (-32767..32767)
	-- LSB units of 10cm
	-- A straight path to use value of 32767
	
	--DE_RoadRegulatorID
	RoadRegulatorID ::= INTEGER (0..65535)
	-- The value zero shall be used for testing only
	
	--DT_SourceType
	SourceType ::= ENUMERATED {
		unknown (0),  -- 0 Unknown
		selfinfo (1), -- 1 information from itself
		v2x (2), -- 2 v2x
		video (3), -- 3 video
		microwaveRadar (4), -- 4 radar
		loop (5), -- 5 loop
		...
		}
	
	--DE_Speed
	Speed ::= INTEGER (0..8191)
	-- Units of 0.02 m/s
	-- The value 8191 indicates that
	-- speed is unavailable
	
	--DE_SpeedConfidence
	SpeedConfidence ::= ENUMERATED {
		unavailable (0), -- Not Equipped or unavailable
		prec100ms (1), -- 100 meters / sec
		prec10ms (2), -- 10 meters / sec
		prec5ms (3), -- 5 meters / sec
		prec1ms (4), -- 1 meters / sec
		prec0-1ms (5), -- 0.1 meters / sec
		prec0-05ms (6), -- 0.05 meters / sec
		prec0-01ms (7) -- 0.01 meters / sec
		}-- Encoded as a 3 bit value
	
	--DE_SpeedLimitType
	SpeedLimitType ::= ENUMERATED {
		unknown, -- Speed limit type not available
		maxSpeedInSchoolZone, -- Only sent when the limit is active
		maxSpeedInSchoolZoneWhenChildrenArePresent, -- Sent at any time
		maxSpeedInConstructionZone, -- Used for work zones, incident zones, etc.
		-- where a reduced speed is present
		vehicleMinSpeed,
		vehicleMaxSpeed, -- Regulatory speed limit for general traffic
		vehicleNightMaxSpeed,
		truckMinSpeed,
		truckMaxSpeed,
		truckNightMaxSpeed,
		vehiclesWithTrailersMinSpeed,
		vehiclesWithTrailersMaxSpeed,
		vehiclesWithTrailersNightMaxSpeed,
		...
		}
					
	--DE_StabilityControlStatus
	StabilityControlStatus ::= ENUMERATED {
		unavailable (0), -- B'00 Not Equipped with SC
		-- or SC status is unavailable
		off (1), -- B'01 Off
		on (2), -- B'10 On or active (but not engaged)
		engaged (3) -- B'11 stability control is Engaged
		}
	
	--DE_SteeringWheelAngle
	SteeringWheelAngle ::= INTEGER (-126..127)
	-- LSB units of 1.5 degrees, a range of -189 to +189 degrees
	-- +001 = +1.5 deg
	-- -126 = -189 deg and beyond
	-- +126 = +189 deg and beyond
	-- +127 to be used for unavailable
	
	--DE_SteeringWheelAngleConfidence
	SteeringWheelAngleConfidence ::= ENUMERATED {
		unavailable (0), -- B'00 Not Equipped with Wheel angle
		-- or Wheel angle status is unavailable
		prec2deg (1), -- B'01 2 degrees
		prec1deg (2), -- B'10 1 degree
		prec0-02deg (3) -- B'11 0.02 degrees
	}-- Encoded as a 2 bit value
	
	--DE_TimeConfidence
	TimeConfidence ::= ENUMERATED{
		unavailable (0), -- NOT Equipped or unavailable
		time-100-000 (1), -- Better than 100 Seconds
		time-050-000 (2), -- Better than 50 Seconds
		time-020-000 (3), -- Better than 20 Seconds
		time-010-000 (4), -- Better than 10 Seconds
		time-002-000 (5), -- Better than 2 Seconds
		time-001-000 (6), -- Better than 1 Seconds
		time-000-500 (7), -- Better than 0.5 Seconds
		time-000-200 (8), -- Better than 0.2 Seconds
		time-000-100 (9), -- Better than 0.1 Seconds
		time-000-050 (10), -- Better than 0.05 Seconds
		time-000-020 (11), -- Better than 0.02 Seconds
		time-000-010 (12), -- Better than 0.01 Seconds
		time-000-005 (13), -- Better than 0.005 Seconds
		time-000-002 (14), -- Better than 0.002 Seconds
		time-000-001 (15), -- Better than 0.001 Seconds
		-- Better than one millisecond
		time-000-000-5 (16), -- Better than 0.000,5 Seconds
		time-000-000-2 (17), -- Better than 0.000,2 Seconds
		time-000-000-1 (18), -- Better than 0.000,1 Seconds
		time-000-000-05 (19), -- Better than 0.000,05 Seconds
		time-000-000-02 (20), -- Better than 0.000,02 Seconds
		time-000-000-01 (21), -- Better than 0.000,01 Seconds
		time-000-000-005 (22), -- Better than 0.000,005 Seconds
		time-000-000-002 (23), -- Better than 0.000,002 Seconds
		time-000-000-001 (24), -- Better than 0.000,001 Seconds
		-- Better than one micro second
		time-000-000-000-5 (25), -- Better than 0.000,000,5 Seconds
		time-000-000-000-2 (26), -- Better than 0.000,000,2 Seconds
		time-000-000-000-1 (27), -- Better than 0.000,000,1 Seconds
		time-000-000-000-05 (28), -- Better than 0.000,000,05 Seconds
		time-000-000-000-02 (29), -- Better than 0.000,000,02 Seconds
		time-000-000-000-01 (30), -- Better than 0.000,000,01 Seconds
		time-000-000-000-005 (31), -- Better than 0.000,000,005 Seconds
		time-000-000-000-002 (32), -- Better than 0.000,000,002 Seconds
		time-000-000-000-001 (33), -- Better than 0.000,000,001 Seconds
		-- Better than one nano second
		time-000-000-000-000-5 (34), -- Better than 0.000,000,000,5 Seconds
		time-000-000-000-000-2 (35), -- Better than 0.000,000,000,2 Seconds
		time-000-000-000-000-1 (36), -- Better than 0.000,000,000,1 Seconds
		time-000-000-000-000-05 (37), -- Better than 0.000,000,000,05 Seconds
		time-000-000-000-000-02 (38), -- Better than 0.000,000,000,02 Seconds
		time-000-000-000-000-01 (39) -- Better than 0.000,000,000,01 Seconds
		}
	
	--DE_TimeMark
	TimeMark ::= INTEGER (0..36001)
	-- Tenths of a second in the current or next hour
	-- In units of 1/10th second from UTC time
	-- A range of 0~36000 covers one hour
	-- The values 35991..35999 are used when a leap second occurs
	-- The value 36000 is used to indicate time >3600 seconds
	-- 36001 is to be used when value undefined or unknown
	-- Note that this is NOT expressed in GPS time
	-- or in local time
	
	--DE_TimeOffset
	TimeOffset ::= INTEGER (1..65535)
	-- LSB units of of 10 mSec,
	-- with a range of 0.01 seconds to 10 minutes and 55.34 seconds
	-- a value of 65534 to be used for 655.34 seconds or greater
	-- a value of 65535 to be unavailable
	
	--DE_TractionControlStatus
	TractionControlStatus ::= ENUMERATED {
		unavailable (0), -- B'00 Not Equipped with traction control
		-- or traction control status is unavailable
		off (1), -- B'01 traction control is Off
		on (2), -- B'10 traction control is On (but not Engaged)
		engaged (3) -- B'11 traction control is Engaged
	}
	
	--DE_TransmissionState
	TransmissionState ::= ENUMERATED {
		neutral (0), -- Neutral
		park (1), -- Park
		forwardGears (2), -- Forward gears
		reverseGears (3), -- Reverse gears
		reserved1 (4),
		reserved2 (5),
		reserved3 (6),
		unavailable (7)-- not-equipped or unavailable value,
		-- Any related speed is relative to the vehicle reference frame used
	}
	
	--DE_VehicleEventFlags
	VehicleEventFlags ::= BIT STRING {
	eventHazardLights (0),
	eventStopLineViolation (1), -- Intersection Violation
	eventABSactivated (2),
	eventTractionControlLoss (3),
	eventStabilityControlactivated (4),
	eventHazardousMaterials (5),
	eventReserved1 (6),
	eventHardBraking (7),
	eventLightsChanged (8),
	eventWipersChanged (9),
	eventFlatTire (10),
	eventDisabledVehicle (11), -- The DisabledVehicle DF may also be sent
	eventAirBagDeployment (12)
	} (SIZE (13, ...))
	
	
	--DE_VehicleHeight 
	VehicleHeight::= INTEGER(0..127)
	-- LSB uints of 5cm, range to 6.35 meters
	
	--DE_VehicleLength
	VehicleLength ::= INTEGER (0.. 4095)
	-- LSB units of 1 cm with a range of >40 meters
	
	--DE_VehicleWidth
	VehicleWidth ::= INTEGER (0..1023)
	-- LSB units are 1 cm with a range of >10 meters
	
	--DE_VerticalAcceleration
	VerticalAcceleration ::= INTEGER (-127..127)
	-- LSB units of 0.02 G steps over -2.52 to +2.54 G
	-- The value +127 shall be used for ranges >= 2.54 G
	-- The value -126 shall be used for ranges <= 2.52 G
	-- The value -127 shall be used for unavailable
	
	--DE_VertOffset-B07
	VertOffset-B07 ::= INTEGER (-64..63)
	-- LSB units of of 10 cm
	-- with a range of +- 6.3 meters vertical
	-- value 63 to be used for 63 or greater
	-- value -63 to be used for -63 or greater
	-- value -64 to be unavailable
	
	--DE_VertOffset-B08
	VertOffset-B08 ::= INTEGER (-128..127)
	-- LSB units of of 10 cm
	-- with a range of +- 12.7 meters vertical
	-- value 127 to be used for 127 or greater
	-- value -127 to be used for -127 or greater
	-- value -128 to be unavailable
	
	--DE_VertOffset-B09
	VertOffset-B09 ::= INTEGER (-256..255)
	-- LSB units of of 10 cm
	-- with a range of +- 25.5 meters vertical
	-- value 255 to be used for 255 or greater
	-- value -255 to be used for -255 or greater
	-- value -256 to be unavailable
	
	--DE_VertOffset-B10
	VertOffset-B10 ::= INTEGER (-512..511)
	-- LSB units of of 10 cm
	-- with a range of +- 51.1 meters vertical
	-- value 511 to be used for 511 or greater
	-- value -511 to be used for -511 or greater
	-- value -512 to be unavailable
	
	--DE_VertOffset-B11
	VertOffset-B11 ::= INTEGER (-1024..1023)
	-- LSB units of of 10 cm
	-- with a range of +- 102.3 meters vertical
	-- value 1023 to be used for 1023 or greater
	-- value -1023 to be used for -1023 or greater
	-- value -1024 to be unavailable
	
	--DE_VertOffset-B12
	VertOffset-B12 ::= INTEGER (-2048..2047)
	-- LSB units of of 10 cm
	-- with a range of +- 204.7 meters vertical
	-- value 2047 to be used for 2047 or greater
	-- value -2047 to be used for -2047 or greater
	-- value -2048 to be unavailable
	
	--DT_YawRate
	YawRate ::= INTEGER (-32767..32767)
	-- LSB units of 0.01 degrees per second (signed)	

END
